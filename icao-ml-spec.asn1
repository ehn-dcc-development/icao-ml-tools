CscaMasterList
         { iso-itu-t(2) international-organization(23) icao(136) mrtd(1)
         security(1) masterlist(2)}
         DEFINITIONS IMPLICIT TAGS ::=
         BEGIN
IMPORTS
          -- Imports from RFC 5280 [PROFILE], Appendix A.1
              Certificate
                FROM PKIX1Explicit88

{ iso(1) identified-organization(3) dod(6)
           internet(1) security(5) mechanisms(5) pkix(7)
             mod(0) pkix1-explicit(18) };

-- CSCA Master List


CscaMasterListVersion ::= INTEGER {v0(0)}


CscaMasterList ::= SEQUENCE {
  version            CscaMasterListVersion,
  certList           SET OF Certificate }

-- Object Identifiers
id-icao-cscaMasterList OBJECT IDENTIFIER ::=
                                 {id-icao-mrtd-security 2}

id-icao-cscaMasterListSigningKey OBJECT IDENTIFIER ::=
                                 {id-icao-mrtd-security 3}

END
